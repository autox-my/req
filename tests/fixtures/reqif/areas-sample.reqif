# Areas sample

# Specification: Main

## D-0: Diagnostics (Heading)

### D-1: Démarrage 起動 (Heading)

#### SW-1 (Requirement)
The R-1 shall hold.

##### SW-2 (Requirement)
The R-2 shall hold.

### SW-3 (Requirement)
The R-3 shall hold.

### SW-5 (Requirement)
The R-5 shall hold.

## SW-4 (Requirement)
The R-4 shall hold.

## H-2: Interfaces (Heading)

## SW-6 (Requirement)
The R-6 shall hold.
